module tsn {
	namespace "http://nxp.com/ns/yang/tsn";
	
	prefix "nxp";
	
	import ietf-yang-types {
		prefix yang;
	}
	import ieee802-dot1q-types {
		prefix dot1q-types;
	}
	import ietf-interfaces {
		prefix if;
	}
	import ieee802-dot1q-preemption {
		prefix preemption;
	}

	import ieee802-dot1q-sched{
			prefix "sched";
	}

	revision 2019-03-29 {
			description "release with OpenIL-v1.5";
	}
	
	feature scheduled-traffic {
		description
		  "Each Port supports the Enhancements for Scheduled Traffic.";
		reference
		  "IEEE Std 802.1Qbv-2015";
	}
	
	container tsn {
		leaf device-id {
			type string;
		}
		
		/* Configuration data nodes */
		container interfaces {
			description
				"Interface configuration parameters.";
				
			list interface{
			
				key "name";
				
				description
					"The list of configured interfaces on the device.";
					
				leaf name {
					type string;
					description
					  "The name of the interface.

					   A device MAY restrict the allowed values for this leaf,
					   possibly depending on the type of the interface.
					   For system-controlled interfaces, this leaf is the
					   device-specific name of the interface.  The 'config false'
					   list /interfaces-state/interface contains the currently
					   existing interfaces on the device.

					   If a client tries to create configuration for a
					   system-controlled interface that is not present in the
					   /interfaces-state/interface list, the server MAY reject
					   the request if the implementation does not support
					   pre-provisioning of interfaces or if the name refers to
					   an interface that can never exist in the system.  A
					   NETCONF server MUST reply with an rpc-error with the
					   error-tag 'invalid-value' in this case.

					   If the device supports pre-provisioning of interface
					   configuration, the 'pre-provisioning' feature is
					   advertised.

					   If the device allows arbitrarily named user-controlled
					   interfaces, the 'arbitrary-names' feature is advertised.

					   When a configured user-controlled interface is created by
					   the system, it is instantiated with the same name in the
					   /interface-state/interface list.";
				}
				
				leaf description {
					type string;
					
					description
						"A textual description of the interface.";
						
					reference
						"RFC 2863: The Interfaces Group MIB - ifAlias";
				}
				
				/* qbv parameters */
				
				leaf gate-enabled{
					type boolean;
					default "true";
						description
							 "The GateEnabled parameter determines whether traffic scheduling is
								active (true) or inactive (false).  The value of this object MUST be
								retained across reinitializations of the management system.";
						reference
							"RFC 2863: The Interfaces Group MIB - ifAdminStatus";
				}
				
				list max-sdu-table {
					key "traffic-class";
					description
						"A list containing a set of max SDU parameters, one for each
						traffic class. All writable objects in this table must be
						persistent over power up restart/reboot.";
					reference
						"IEEE Std 802.1Qbv-2015:
						   Clause 12.29.1
						   Clause 8.6.8.4
						   Clause 8.6.9";
					leaf traffic-class {
						type dot1q-types:traffic-class-type;
						description
						  "Traffic class";
					}
					leaf queue-max-sdu {
						type uint32;
						default "0";
						description
							"The value of the queueMaxSDU parameter for the traffic
							class. A value of 0 is interpreted as the max SDU size
							supported by the underlying MAC. The value must be retained
							across reinitializations of the management system.";
						reference
							"IEEE Std 802.1Qbv-2015:
								 Clause 12.29.1.1.1
								 Clause 8.6.8.4
								 Clause 8.6.9";
					}
				}
				
				leaf config-change {
					type boolean;
					description
					  "The ConfigChange parameter signals the start of a
					  configuration change when it is set to TRUE, indicating that
					  the administrative parmaeters for the Port are ready to be
					  copied into their corresponding operational parameters. This
					  should only be done when the various administrative
					  parameters are all set to appropriate values.";
					reference
					  "IEEE Std 802.1Qbv-2015:
						 Clause 12.29.1
						 Clause 8.6.9.4.7";
				}
				
				container admin{
					leaf admin-gate-states {
						type uint8;
						description
						  "AdminGateStates is the administrative value of the initial
						  gate states for the Port. The bits of the octet represent
						  the gate states for the corresponding traffic classes; the
						  most-significant bit corresponds to traffic class 7, the
						  least-significant bit to traffic class 0. A bit value of 0
						  indicates closed; a bit value of 1 indicates open. The value
						  must be retained across reinitializations of the management
						  system.";
						reference
						  "IEEE Std 802.1Qbv-2015:
							 Clause 12.29.1
							 Clause 8.6.9.4.5";
					}
					
					leaf admin-control-list-length {
						type uint32;
						description
						  "AdminControlListLength is the number of entries in the
						  AdminControlList. The value must be retained across
						  reinitializations of the management system.";
						reference
						  "IEEE Std 802.1Qbv-2015:
							 Clause 12.29.1.2
							 Clause 8.6.9.4.6";
					}
					/* this parameter will be retained across reinitializations, so
					   we can ignore it */
					container admin-cycle-time {
						description
						  "AdminCycleTime specifies the administrative value of the
						  gating cycle time for the Port.
						  
						  AdminCycleTime is a rational number of seconds, defined by
						  an integer numerator and an integer denominator.
						  
						  The value must be retained across reinitializations of the
						  management system.";
						reference
						  "IEEE Std 802.1Qbv-2015:
							 Clause 12.29.1
							 Clause 8.6.8.4
							 Clause 8.6.9.4.3";
						leaf numerator {
						  type uint32;
						  description
							"AdminCycleTime’s numerator.";
						}
						leaf denominator {
						  type uint32;
						  description
							"AdminCycleTime’s denominator.";
						}
					}
					
					leaf admin-cycle-time-extension {
						type uint32;
						description
						  "An unsigned integer number of nanoseconds, defining the
						  maximum amount of time by which the gating cycle for the
						  Port is permitted to be extended when a new cycle
						  configuration is being installed. This is the administrative
						  value.
						  
						  The value must be retained across reinitializations of the
						  management system.";
						reference
						  "IEEE Std 802.1Qbv-2015:
							 Clause 12.29.1
							 Clause 8.6.9.4.4";
					}
					
					container admin-base-time {
						description
						  "The administrative value of the base time at which gating
						  cycles begin, expressed as an IEEE 1588 precision time
						  protocol (PTP) timescale.
						  
						  The value must be retained across reinitializations of the
						  management system.";
						reference
						  "IEEE Std 802.1Qbv-2015:
							 Clause 12.29.1
							 Clause 8.6.9.4.1";
						uses sched:ptp-timestamp;
					}
	  
					list admin-control-list {
						key "index";
						description
						  "AdminControlList is the administrative value of the gate
						  control list for the Port.
						  
						  The value must be retained across reinitializations of the
						  management system.";
						reference
						  "IEEE Std 802.1Qbv-2015:
							 Clause 12.29.1.2
							 Clause 8.6.8.4
							 Clause 8.6.9.4.2";
						leaf index {
						  type uint32;
						  description
							"This index is provided in order to provide a unique key
							per list entry.
							
							The value of index for each entry shall be unique (but not
							neccesarily contiguous).";
						}
						uses sched:gate-control-entry;
					}
				}
			}
		}
		
		
		/*
		 * Operational state data nodes
		 */
		container interfaces-state {
			config false;
			description
				"Data nodes for the operational state of interfaces.";
				
			list interface{
				config false;
			
				key "name";
				
				description
					"The list of configured interfaces on the device.";
					
				leaf name {
					type string;
					config false;
					description
					  "The name of the interface.

					   A device MAY restrict the allowed values for this leaf,
					   possibly depending on the type of the interface.
					   For system-controlled interfaces, this leaf is the
					   device-specific name of the interface.  The 'config false'
					   list /interfaces-state/interface contains the currently
					   existing interfaces on the device.

					   If a client tries to create configuration for a
					   system-controlled interface that is not present in the
					   /interfaces-state/interface list, the server MAY reject
					   the request if the implementation does not support
					   pre-provisioning of interfaces or if the name refers to
					   an interface that can never exist in the system.  A
					   NETCONF server MUST reply with an rpc-error with the
					   error-tag 'invalid-value' in this case.

					   If the device supports pre-provisioning of interface
					   configuration, the 'pre-provisioning' feature is
					   advertised.

					   If the device allows arbitrarily named user-controlled
					   interfaces, the 'arbitrary-names' feature is advertised.

					   When a configured user-controlled interface is created by
					   the system, it is instantiated with the same name in the
					   /interface-state/interface list.";
				}
				
				leaf description {
					type string;
					config false;
					
					description
						"A textual description of the interface.";
						
					reference
						"RFC 2863: The Interfaces Group MIB - ifAlias";
				}
				
				/* qbv parameters */
				
				container config-change-time {
					config false;
					description
					  "The time at which the next config change is scheduled to
					  occur.";
					reference
					  "IEEE Std 802.1Qbv-2015:
						 Clause 12.29.1
						 Clause 8.6.9.4.9";
					uses sched:ptp-timestamp;
				}
				
				leaf tick-granularity{
					description
					  "The granularity of the cycle time clock, represented as an unsigned
					  number of tenths of nanoseconds.  The value of this object MUST be
					  retained across reinitializations of the management system.";
					  
					type uint32;
				}
				
				container current-time {
					config false;
					description
					  "The current time, in PTPtime, as maintained by the local system.  The
					  value is a representation of a PTPtime value, consisting of a 48-bit
					  integer number of seconds and a 32-bit integer number of nanoseconds.";
					
					uses sched:ptp-timestamp;
				}
				
				leaf config-pending {
					type boolean;
					config false;
					
					description
					  "The value of the ConfigPending state machine variable.  The value is
					  TRUE if a configuration change is in progress but has not yet
					  completed.";
				}
				
				leaf config-change-error {
					type yang:counter64;
					config false;
					description
					  "A counter of the number of times that a re-configuration of
					  the traffic schedule has been requested with the old
					  schedule still running and the requested base time was in
					  the past.";
				}
				
				leaf supported-list-max {
					type uint32;
					config false;
					description
					  "The maximum value supported by this Port for the
					  AdminControlListLength and OperControlListLength parameters.
					  It is available for use by schedule computation software to
					  determine the port’s control list capacity prior to
					  computation.";
				}
				
				container oper{
					leaf oper-gate-states {
						type uint8;
						config false;
						description
						  "OperGateStates is the operational value of the current gate
						  states for the Port. The bits of the octet represent the
						  gate states for the corresponding traffic classes; the
						  most-significant bit corresponds to traffic class 7, the
						  least-significant bit to traffic class 0. A bit value of 0
						  indicates closed; a bit value of 1 indicates open. The value
						  must be retained across reinitializations of the management
						  system.";
					}
					
					leaf oper-control-list-length {
						type uint32;
						config false;
						description
						  "OperControlListLength is the number of entries in the
						  OperControlList.";
						reference
						  "IEEE Std 802.1Qbv-2015:
							 Clause 12.29.1.2
							 Clause 8.6.9.4.23";
					}
					
					container oper-cycle-time {
						config false;
						description
						  "OperCycleTime specifies the operational value of the gating
						  cycle time for the Port.
						  
						  OperCycleTime is a rational number of seconds, defined by an
						  integer numerator and an integer denominator.";
						reference
						  "IEEE Std 802.1Qbv-2015:
							 Clause 12.29.1
							 Clause 8.6.8.4
							 Clause 8.6.9.4.20";
						leaf numerator {
						  type uint32;
						  description
							"OperCycleTime’s numerator.";
						}
						leaf denominator {
						  type uint32;
						  description
							"OperCycleTime’s denominator.";
						}
					}
					
					leaf oper-cycle-time-extension {
						type uint32;
						config false;
						description
						  "An unsigned integer number of nanoseconds, defining the
						  maximum amount of time by which the gating cycle for the
						  Port is permitted to be extended when a new cycle
						  configuration is being installed. This is the operational
						  value.";
						reference
						  "IEEE Std 802.1Qbv-2015:
							 Clause 12.29.1
							 Clause 8.6.9.4.21";
					}
					
					container oper-base-time {
						config false;
						description
						  "The operational value of the base time at which gating
						  cycles begin, expressed as an IEEE 1588 precision time
						  protocol (PTP) timescale.";
						reference
						  "IEEE Std 802.1Qbv-2015:
							 Clause 12.29.1
							 Clause 8.6.9.4.18";
						uses sched:ptp-timestamp;
					}
	  
					list oper-control-list {
						key "index";
						config false;
						description
						  "OperControlList is the operational value of the gate
						  control list for the Port.";
						reference
						  "IEEE Std 802.1Qbv-2015:
							 Clause 12.29.1.2
							 Clause 8.6.8.4
							 Clause 8.6.9.4.19";
						leaf index {
							type uint32;
							description
								"This index is provided in order to provide a unique key
								per list entry.
								
								The value of index for each entry shall be unique (but not
								neccesarily contiguous).";						
						}
						uses sched:gate-control-entry;
					}
				}
			}
		}
	}
	/* Add RPC command */
	rpc get_ports_name {
		description
			"get available ports names";
		output {
			container ports_name{
				config false;
				leaf-list name{ type string; }
			}
		}
	}
	rpc validate_config {
		description
			"validate configuration in candidate datastore";
	}
	
	rpc apply_config {
		description
			"apply configuration in running datastore";
	}
}
